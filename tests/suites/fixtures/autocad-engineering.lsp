;; Deterministic integration fixture, created only in a copied sample drawing.
(defun dhcb-qa-create (out / block layer specs spec pt insert handle f rows index parentHandle)
  (setvar "TILEMODE" 1)
  (setvar "INSUNITS" 4)
  (setq block "DHCB-QA-ENGINEERING" layer "DHCB-QA-ENGINEERING")
  (if (tblsearch "BLOCK" block) (error "Fixture block already exists; use a fresh sample copy."))
  (entmake (list '(0 . "LAYER") '(100 . "AcDbSymbolTableRecord") '(100 . "AcDbLayerTableRecord") (cons 2 layer) '(70 . 0) '(62 . 3) '(6 . "Continuous")))
  (entmake (list '(0 . "BLOCK") (cons 2 block) '(70 . 2) '(10 0.0 0.0 0.0)))
  (foreach tag '("NUM" "NOTE")
    (entmake (list '(0 . "ATTDEF") '(8 . "0") '(10 0.0 0.0 0.0) '(40 . 10.0) '(1 . "UNSET") (cons 2 tag) (cons 3 tag) '(70 . 0))))
  (entmake '((0 . "ENDBLK")))
  ;; Insert in deliberately scrambled order; numbering must follow geometry.
  (setq specs '(((2000.0 0.0 0.0) "EQ-03" "plain-three") ((0.0 1000.0 0.0) "EQ-01" "DHCB-QA-OLD") ((1000.0 1000.0 0.0) "EQ-02" "plain-two")))
  (setq rows nil index 0)
  (foreach spec specs
    (setq pt (car spec))
    (entmake (list '(0 . "INSERT") (cons 2 block) (cons 8 layer) '(66 . 1) (cons 10 pt) '(41 . 1.0) '(42 . 1.0) '(43 . 1.0)))
    (foreach pair (list (cons "NUM" "UNSET") (cons "NOTE" (caddr spec)))
      (entmake (list '(0 . "ATTRIB") (cons 8 layer) (cons 10 pt) '(40 . 10.0) (cons 1 (cdr pair)) (cons 2 (car pair)) '(70 . 0))))
    (entmake '((0 . "SEQEND")))
    ;; INSERT becomes entlast only after its ATTRIB/SEQEND sequence is complete.
    (setq insert (entlast) handle (cdr (assoc 5 (entget insert))))
    (setq rows (cons (list handle (cadr spec) (caddr spec)) rows)))
  (entmake (list '(0 . "TEXT") (cons 8 layer) '(10 0.0 2000.0 0.0) '(40 . 10.0) '(1 . "DHCB-QA-OLD")))
  (entmake (list '(0 . "MTEXT") '(100 . "AcDbEntity") (cons 8 layer) '(100 . "AcDbMText") '(10 1000.0 2000.0 0.0) '(40 . 10.0) '(41 . 100.0) '(71 . 1) '(1 . "{\\H2.5x;DHCB-QA-OLD}")))
  ;; A match spanning two formatting runs must be reported as skipped, not complete.
  (entmake (list '(0 . "MTEXT") '(100 . "AcDbEntity") (cons 8 layer) '(100 . "AcDbMText") '(10 2000.0 2000.0 0.0) '(40 . 10.0) '(41 . 100.0) '(71 . 1) '(1 . "{\\H2.5x;DHCB-QA-FOR}{\\H0.7x;MATTED}")))
  (setq f (open (strcat out "/fixture-expected.csv") "w"))
  (write-line "Handle,Number,InitialNote" f)
  (foreach row rows (write-line (strcat (car row) "," (cadr row) "," (caddr row)) f))
  (close f)
  (setq f (open (strcat out "/attributes-edit.csv") "w"))
  (write-line "BlockName,Handle,AttributeTag,AttributeValue" f)
  (foreach row rows
    (if (= (caddr row) "DHCB-QA-OLD")
      (write-line (strcat block "," (car row) ",NOTE,\"DHCB-QA-CSV, \"\"quoted\"\"\"") f)))
  (close f)
  (setq f (open (strcat out "/attributes-incomplete.csv") "w"))
  (write-line "BlockName,Handle,AttributeTag,AttributeValue" f)
  (write-line "broken,row,three-columns" f)
  (write-line (strcat block ",7FFFFFFF,NOTE,missing-handle") f)
  (write-line (strcat block "," (caar rows) ",MISSING,missing-tag") f)
  (close f)
  ;; Separate already-correct target proves a layer lock does not turn a no-op partial.
  (entmake '((0 . "BLOCK") (2 . "DHCB-QA-NOOP") (70 . 2) (10 0.0 0.0 0.0)))
  (foreach tag '("NUM" "NOTE")
    (entmake (list '(0 . "ATTDEF") '(8 . "0") '(10 0.0 0.0 0.0) '(40 . 10.0) '(1 . "UNSET") (cons 2 tag) (cons 3 tag) '(70 . 0))))
  (entmake '((0 . "ENDBLK")))
  (entmake (list '(0 . "INSERT") '(2 . "DHCB-QA-NOOP") (cons 8 layer) '(66 . 1) '(10 4000.0 4000.0 0.0) '(41 . 1.0) '(42 . 1.0) '(43 . 1.0)))
  (foreach pair '(("NUM" . "EQ-01") ("NOTE" . "stable"))
    (entmake (list '(0 . "ATTRIB") (cons 8 layer) '(10 4000.0 4000.0 0.0) '(40 . 10.0) (cons 1 (cdr pair)) (cons 2 (car pair)) '(70 . 0))))
  (entmake '((0 . "SEQEND")))
  ;; Typical attributed block: INSERT is on a locked layer, attributes inherit layer 0.
  (entmake '((0 . "BLOCK") (2 . "DHCB-QA-PARENT-LOCK") (70 . 2) (10 0.0 0.0 0.0)))
  (foreach tag '("NUM" "NOTE")
    (entmake (list '(0 . "ATTDEF") '(8 . "0") '(10 0.0 0.0 0.0) '(40 . 10.0) '(1 . "UNSET") (cons 2 tag) (cons 3 tag) '(70 . 0))))
  (entmake '((0 . "ENDBLK")))
  (entmake (list '(0 . "INSERT") '(2 . "DHCB-QA-PARENT-LOCK") (cons 8 layer) '(66 . 1) '(10 5000.0 5000.0 0.0) '(41 . 1.0) '(42 . 1.0) '(43 . 1.0)))
  (foreach pair '(("NUM" . "UNSET") ("NOTE" . "DHCB-QA-PARENT-LOCK"))
    (entmake (list '(0 . "ATTRIB") '(8 . "0") '(10 5000.0 5000.0 0.0) '(40 . 10.0) (cons 1 (cdr pair)) (cons 2 (car pair)) '(70 . 0))))
  (entmake '((0 . "SEQEND")))
  (setq parentHandle (cdr (assoc 5 (entget (entlast)))))
  (setq f (open (strcat out "/attributes-parent-lock.csv") "w"))
  (write-line "BlockName,Handle,AttributeTag,AttributeValue" f)
  (write-line (strcat "DHCB-QA-PARENT-LOCK," parentHandle ",NOTE,attempted-parent-locked-write") f)
  (close f)
  ;; Attribute-only source layer must remain in use when its parent INSERT is locked.
  (entmake '((0 . "LAYER") (100 . "AcDbSymbolTableRecord") (100 . "AcDbLayerTableRecord") (2 . "DHCB-QA-ATTRONLY") (70 . 0) (62 . 4) (6 . "Continuous")))
  (entmake '((0 . "BLOCK") (2 . "DHCB-QA-ATTRONLY") (70 . 2) (10 0.0 0.0 0.0)))
  (foreach tag '("NUM" "NOTE")
    (entmake (list '(0 . "ATTDEF") '(8 . "0") '(10 0.0 0.0 0.0) '(40 . 10.0) '(1 . "UNSET") (cons 2 tag) (cons 3 tag) '(70 . 0))))
  (entmake '((0 . "ENDBLK")))
  (entmake (list '(0 . "INSERT") '(2 . "DHCB-QA-ATTRONLY") (cons 8 layer) '(66 . 1) '(10 6000.0 6000.0 0.0) '(41 . 1.0) '(42 . 1.0) '(43 . 1.0)))
  (foreach pair '(("NUM" . "UNSET") ("NOTE" . "attr-only"))
    (entmake (list '(0 . "ATTRIB") '(8 . "DHCB-QA-ATTRONLY") '(10 6000.0 6000.0 0.0) '(40 . 10.0) (cons 1 (cdr pair)) (cons 2 (car pair)) '(70 . 0))))
  (entmake '((0 . "SEQEND")))
  (princ "\nDHCB deterministic fixture created.\n")
  (princ))

(defun dhcb-qa-check-final (out / selection i entity textCount mtextCount f attribute attributeData attributeCount)
  (setq selection (ssget "_X" '((8 . "DHCB-QA-ENGINEERING"))) textCount 0 mtextCount 0 i 0)
  (if (not selection) (error "Fixture entities missing."))
  (if (/= (sslength selection) 9) (error "Fixture entity layers/cardinality changed."))
  (repeat (sslength selection)
    (setq entity (entget (ssname selection i)) i (1+ i))
    (cond
      ((= (cdr (assoc 0 entity)) "INSERT")
        (setq attribute (entnext (cdr (assoc -1 entity))) attributeCount 0)
        (while (and attribute (/= (cdr (assoc 0 (entget attribute))) "SEQEND"))
          (setq attributeData (entget attribute))
          (if (= (cdr (assoc 0 attributeData)) "ATTRIB")
            (progn
              (if (= (cdr (assoc 2 entity)) "DHCB-QA-PARENT-LOCK")
                (progn
                  (if (/= (cdr (assoc 8 attributeData)) "0") (error "Parent-locked attribute layer changed."))
                  (if (/= (cdr (assoc 1 attributeData)) (if (= (cdr (assoc 2 attributeData)) "NUM") "UNSET" "DHCB-QA-PARENT-LOCK"))
                    (error "Attribute changed despite parent INSERT layer lock.")))
                (if (= (cdr (assoc 2 entity)) "DHCB-QA-ATTRONLY")
                  (progn
                    (if (/= (cdr (assoc 8 attributeData)) "DHCB-QA-ATTRONLY") (error "Attribute-only source layer changed."))
                    (if (/= (cdr (assoc 1 attributeData)) (if (= (cdr (assoc 2 attributeData)) "NUM") "UNSET" "attr-only")) (error "Attribute-only value changed.")))
                  (if (/= (cdr (assoc 8 attributeData)) "DHCB-QA-ENGINEERING") (error "Fixture attribute layer changed."))))
              (setq attributeCount (1+ attributeCount))))
          (setq attribute (entnext attribute)))
        (if (/= attributeCount 2) (error "Fixture attribute cardinality changed.")))
      ((= (cdr (assoc 0 entity)) "TEXT")
        (if (/= (cdr (assoc 1 entity)) "DHCB-QA-OLD") (error "DBText restoration failed."))
        (setq textCount (1+ textCount)))
      ((= (cdr (assoc 0 entity)) "MTEXT")
        (if (not (member (cdr (assoc 1 entity)) '("{\\H2.5x;DHCB-QA-OLD}" "{\\H2.5x;DHCB-QA-FOR}{\\H0.7x;MATTED}"))) (error "MText value/formatting restoration failed."))
        (setq mtextCount (1+ mtextCount)))))
  (if (or (/= textCount 1) (/= mtextCount 2)) (error "Fixture text cardinality incorrect."))
  (setq f (open (strcat out "/fixture-final-ok.txt") "w"))
  (write-line "DBText restored; MText value and height formatting preserved." f)
  (close f)
  (princ))

(defun dhcb-qa-lock (/ record flags)
  (setq record (entget (tblobjname "LAYER" "DHCB-QA-ENGINEERING")))
  (setq flags (assoc 70 record))
  (if (not (entmod (subst (cons 70 (logior 4 (cdr flags))) flags record)))
    (error "Could not lock fixture layer."))
  (princ))
